SICCT-Protocol-1-3-0 DEFINITIONS IMPLICIT TAGS ::= BEGIN

 
 
 
 
 

 
SicctMessageType ::= ENUMERATED {
    c-command   (107),    
    r-command   (131),    
    event        (80)     
}

 
 
 
 
SicctFuAddress ::= INTEGER (0..65535)

 
 
SicctSequenceNumber ::= INTEGER (0..65535)

SicctEnvelope ::= SEQUENCE {
    bMessageType    SicctMessageType,        
    wSrcOrDesAddr   SicctFuAddress,          
    wSeq            SicctSequenceNumber,     
    abRFU           OCTET STRING (SIZE(1)),  
    dwLength        INTEGER (0..4294967295), 
                                             
    abCmd           SicctPayload             
}

 
SicctPayload ::= CHOICE {
    commandApdu     CommandAPDU,             
    iso7816Apdu     OCTET STRING,            
    responseApdu    ResponseAPDU,            
    eventData       EventNotification        
}

 
 
 
 

 
SicctClass ::= INTEGER { sicct (128), ehealth (129) } (0..255)

 
SicctInstruction ::= ENUMERATED {
    reset-ct-icc                (17),    
    request-icc                 (18),    
    get-status                  (19),    
    eject-icc                   (21),    
    input                       (22),    
    output                      (23),    
    perform-verification        (24),    
    modify-verification-data    (25),    
    select-ct-mode              (32),    
    comfort-authentication      (33),    
    comfort-enroll              (34),    
    set-status                  (35),    
    download-init               (36),    
    download-data               (37),    
    download-finish             (38),    
    control-command             (39),    
    init-ct-session             (40),    
    close-ct-session            (41),    
     
    ehealth-terminal-authenticate (170)  
}

 
 
CommandHeader ::= SEQUENCE {
    cla     SicctClass,
    ins     SicctInstruction,
    p1      INTEGER (0..255),    
    p2      INTEGER (0..255)     
}

 
 
 
CommandAPDU ::= SEQUENCE {
    header      CommandHeader,
    commandData SEQUENCE OF SicctDataObject OPTIONAL    
     
}

 
StatusWord ::= SEQUENCE {
    sw1     INTEGER (0..255),
    sw2     INTEGER (0..255)
}

ResponseAPDU ::= SEQUENCE {
    responseData    SEQUENCE OF SicctDataObject OPTIONAL,   
    trailer         StatusWord                              
}

 
 
 
 

 
 
SicctDataObject ::= CHOICE {
    atr         ATR-DO,
    hb          HB-DO,
    ctm         CTM-DO,
    appl        APPL-DO,
    cmd         CMD-DO,
    ppsr        PPSR-DO,
    iccs        ICCS-DO,         
    fu          FU-DO,
    clif        CLIF-DO,
    fui         FUI-DO,
    cs          CS-DO,
    smtbd       SMTBD-DO,
    fuName      FU-NAME-DO,
    fuCon       FU-CON-DO,
    cts         CTS-DO,
    intfs       INTFS-DO,
    intfc       INTFC-DO,
    dsplc       DSPLC-DO,
    seqno       SEQNO-DO,
    ctsess      CTSESS-DO,
    kpc         KPC-DO,
    dlparam     DLPARAM-DO,      
    dldata      DLDATA-DO,       
    dlterm      DLTERM-DO,
     
    ss          SS-DO,           
    ssc         SSC-DO,          
    ssr         SSR-DO           
}

 
 
ATR-DO ::= [APPLICATION 65] IMPLICIT OCTET STRING (SIZE(0..255))

 
 
HB-DO ::= [APPLICATION 82] IMPLICIT OCTET STRING (SIZE(0..252))

 
 
CTM-DO ::= [APPLICATION 6] IMPLICIT SEQUENCE {
    ctm     OCTET STRING (SIZE(5)),          
    ctt     OCTET STRING (SIZE(5)),          
    ctsv    OCTET STRING (SIZE(5)),          
    dd      OCTET STRING (SIZE(0..112)) OPTIONAL   
}
 

 
 
APPL-DO ::= [APPLICATION 16] IMPLICIT OCTET STRING

 
 
CMD-DO ::= [APPLICATION 18] IMPLICIT OCTET STRING

 
 
PPSR-DO ::= [APPLICATION 19] IMPLICIT OCTET STRING

 
 
 
ICCS-DO ::= [0] IMPLICIT OCTET STRING (SIZE(1..255))
 
 

 
 
 
WT-DO ::= [0] IMPLICIT OCTET STRING (SIZE(1..255))

 
 
 
FU-DO ::= [1] IMPLICIT OCTET STRING (SIZE(0..512))

 
 
CLIF-DO ::= [3] IMPLICIT OCTET STRING

 
 
 
FUI-DO ::= [4] IMPLICIT SEQUENCE {
    fuType  INTEGER (0..255),
    fuIndex INTEGER (0..255)
}
 

 
 
CS-DO ::= [5] IMPLICIT OCTET STRING

 
 
 
SMTBD-DO ::= [0] IMPLICIT SEQUENCE {
    appl    APPL-DO,
    cs      CS-DO OPTIONAL
}

 
 
FU-NAME-DO ::= [1] IMPLICIT SEQUENCE {
    fui     FUI-DO,
    name    [1] IMPLICIT PrintableString (SIZE(0..32))    
}

 
 
FU-CON-DO ::= [2] IMPLICIT SEQUENCE (SIZE(2..3)) OF FUI-DO

 
 
CTS-DO ::= [APPLICATION 3] IMPLICIT SEQUENCE {
    fu      FU-DO OPTIONAL,
    iccs    ICCS-DO,
    clif    CLIF-DO OPTIONAL
}

 
 
INTFS-DO ::= [APPLICATION 5] IMPLICIT OCTET STRING

 
 
 
INTFC-DO ::= [APPLICATION 6] IMPLICIT OCTET STRING

 
 
DSPLC-DO ::= [APPLICATION 7] IMPLICIT OCTET STRING

 
 
 
 
 
SEQNO-DO ::= [APPLICATION 8] IMPLICIT SEQUENCE {
    commandSequenceNumber       OCTET STRING (SIZE(2)),   
    commandSequenceStatusWord   OCTET STRING (SIZE(0..2)) OPTIONAL
         
         
}

 
 
CTSESS-DO ::= [APPLICATION 9] IMPLICIT SEQUENCE {
    username    [UNIVERSAL 19] IMPLICIT OCTET STRING,
    password    [UNIVERSAL 19] IMPLICIT OCTET STRING,
    session-id  [UNIVERSAL 19] IMPLICIT OCTET STRING
}

 
 
KPC-DO ::= [APPLICATION 10] IMPLICIT OCTET STRING

 
 
 
DLPARAM-DO ::= [APPLICATION 19] IMPLICIT SEQUENCE {
    timeoutSeconds      OCTET STRING (SIZE(1..2)),   
    maxDownloadDataSize OCTET STRING (SIZE(1..2))    
}

 
 
DLDATA-DO ::= [APPLICATION 19] IMPLICIT OCTET STRING (SIZE(0..65531))

 
 
DLTERM-DO ::= [APPLICATION 19] IMPLICIT SEQUENCE {
    timeoutSeconds  OCTET STRING (SIZE(0..1)) OPTIONAL
}

 
 
 
 
 
 
 
 
 
 
 
 
 
 
 
 
 
 
 
 
 
 
 
 
 
 
 

 
EhealthTerminalAuthenticateP2 ::= ENUMERATED {
    create              (1),     
    validate            (2),     
    generate-challenge  (3),     
    add                 (4)      
}

 
 
 
 
 
 
SS-DO ::= [PRIVATE 20] IMPLICIT OCTET STRING (SIZE(16))

 
 
 
 
 
 
SSC-DO ::= [PRIVATE 21] IMPLICIT OCTET STRING (SIZE(16..127))

 
 
 
 
 
 
SSR-DO ::= [PRIVATE 22] IMPLICIT OCTET STRING (SIZE(32))

 
 
 
 
 
 

EventNotification ::= CHOICE {
     
    keepAlive       [0] IMPLICIT FuNumber,         
    terminalSignOff [1] IMPLICIT FuNumber,         
    protocolError   [6] IMPLICIT ProtocolErrorCode,  

     
    fuAdded         [2] IMPLICIT FuNumber,         
    fuRemoved       [3] IMPLICIT FuNumber,         
    cardInserted    [4] IMPLICIT FuNumber,         
    cardRemoved     [5] IMPLICIT FuNumber,         

     
    keypadEvent     [7] IMPLICIT KeypadEvent       
}

FuNumber ::= OCTET STRING (SIZE(2))    

ProtocolErrorCode ::= ENUMERATED {
    timeout-reading-envelope    (0),     
    timeout-reading-data        (1),     
    unsupported-message-type    (16),    
    address-fu-not-present      (17),    
    wrong-sequence-number       (18)     
}

KeypadEvent ::= SEQUENCE {
    fuNumber    FuNumber,                
    keyCode     INTEGER (0..255)         
}

END
